module ieee802-dot1ax-linkagg {
  yang-version 1.1;
  namespace "urn:ieee:params:xml:ns:yang:ieee802-dot1ax-linkagg";
  prefix "dot1ax";

  import ieee802-dot1ax-types {
    prefix "ax";
  }
  import ieee802-types {
    prefix "ieee";
  }
  import ietf-yang-types {
    prefix "yang";
  }
  import ietf-interfaces {
    prefix "if";
  }
  import iana-if-type {
    prefix "ianaif";
  }

  organization
    "Institute of Electrical and Electronics Engineers";

  contact
      "Web URL: http://www.ieee802.org/1/

       Working Group Chair:
        Glenn Parsons
        glenn.parsons@ericsson.com

       Editor:
         Stephen Haddock
         shaddock@stanfordalumni.org";

  description
    "This YANG module describes the configuration model for Link 
    Aggregation, as specified in IEEE Std 802.1AX, including Link
    Aggregation Control Protocol (LACP) and Conversation Sensitive
    Collection and Distribution. 
    
    Copyright (C) IEEE (2024).
    
    This version of this YANG module is part of IEEE Std 802.1AX;
    see the standard itself for full legal notices.";


  revision "2024-06-05" {
    description
      "For task group ballot on draft 0.1";
    reference
      "IEEE 802.1AX-2020, Link Aggregation.";
  }
  revision "2024-05-04" {
    description
      "Initial Version.";
    reference
      "IEEE 802.1AX-2020, Link Aggregation.";
  }

  typedef key-group-ref {
    type leafref {
      path "/dot1ax:linkagg/dot1ax:key-group/dot1ax:name";
    }
    description
      "This type is used by aggregators and aggregation ports to
      reference an entry in the key-group list.";
  }


  container linkagg {
    description
      "LAG System specific configuration nodes.";
    list key-group {
      key name;
      unique "actor-system-id actor-admin-key";
      description
        "List of key groups.  A key group is the set of aggregators
        and aggregation ports that share the same system priority, 
        system identifier, and aggregation key, and therefore can 
        potentially form a Link Aggregation Group.  Each entry in 
        the key group list contains the parameters common to all 
        aggregation ports and/or aggregatiors in the key group.";
      leaf name {  
        type string;
        description
          "Name for the key group.";
      }
      leaf actor-admin-key {
        type uint16;
        mandatory true;
        description
          "The current administrative value of the Key for the
          Aggregator. The administrative Key value may differ
          from the operational Key value for the reasons
          discussed in 5.6.2. The meaning of particular Key
          values is of local significance.";
        reference
          "IEEE 802.1AX-2020, Clause 7.3.1.1.7
           IEEE 802.1AX-2020, Clause 7.3.2.1.4";
      }
      leaf actor-system-id {
        type ieee:mac-address;
        mandatory true;
        description
          "The unique identifier for the aggregating system.";
        reference
          "IEEE 8021AX-2020, Clause 7.3.1.1.4
           IEEE 8021AX-2020, Clause 7.3.2.1.3";
      }
      leaf actor-system-priority {
        type uint16;
        default 1;  
       description
          "The priority of the aggregating system.";
        reference
          "IEEE 802.1AX-2020, Clause 7.3.1.1.5
           IEEE 802.1AX-2020, Clause 7.3.2.1.2";
      }
      leaf actor-protocol-da {
        type ieee:mac-address;
        must 
          '. = "01-80-c2-00-00-00" or . = "01-80-C2-00-00-00" or
           . = "01-80-c2-00-00-02" or . = "01-80-C2-00-00-02" or
           . = "01-80-c2-00-00-03" or . = "01-80-C2-00-00-03"' {
            error-message "Invalid protocol address";
        }
        default "01-80-c2-00-00-02";  
        description
          "A 6-octet read-write MAC Address value specifying the DA
          to be used when sending Link Aggregation Control and 
          Marker PDUs.  Valid addresses are the Nearest Customer
          Bridge, Slow_Protocols_Multicast, and Nearest non-TPMR
          Bridge group addresses.  The default value 
          shall be the Slow_Protocols_Multicast address.";
        reference
          "IEEE 802.1AX-2020, Clause 7.3.2.2.1, Clause 6.2.10.2";
      }
      leaf collector-max-delay {
        type uint16;
        description
          "Defines the maximum delay, in tens of microseconds,
          that may be imposed by the Frame Collector between
          receiving a frame from an Aggregator Parser, and
          either delivering the frame to its MAC Client or
          discarding the frame (see 5.2.3.1.1).
          Used to determine the maximum delay for the Marker 
          Protocol to wait for a Marker Response.";
        reference
          "IEEE 802.1AX-2020, Clause 7.3.1.1.32, Clause 6.2.3.1.1,
          Clause B.3";
      }
      leaf partner-admin-system-id {
        type ieee:mac-address;
        default "00-00-00-00-00-00";  
        description
          "The administrative value of the Partners System ID.
          The assigned value is used, along with the value of 
          port-partner-admin-system-id, partner-admin-key, 
          partner-admin-port, and partner-admin-port-priority, 
          to achieve administratively configured Link 
          Aaggregation Groups with a partner that does not run
          LACP.";
        reference
        "IEEE 802.1AX-2020, Clause 7.3.1.1.10
         IEEE 802.1AX-2020, Clause 7.3.2.1.8";
      }
      leaf partner-admin-system-priority { 
        type uint16;
        default 0;
        description  
          "The administrative value of priority associated
          with the Partners System ID. The assigned 
          value is used, along with the value of 
          port-partner-admin-system-id, partner-admin-key, 
          partner-admin-port, and partner-admin-port-priority, 
          to achieve administratively configured Link 
          Aaggregation Groups with a partner that does not run
          LACP.";
        reference
          "IEEE 802.1AX-2020, Clause 7.3.1.1.11
           IEEE 802.1AX-2020, Clause 7.3.2.1.6";
      }
      leaf-list lags {
        type if:interface-ref;
        config false;
        description
          "A list of the if:name of aggregators assigned to this
          key group.";
        reference
          "link-aggregation:key-groups";
      }
      leaf-list aggports {
        type if:interface-ref;
        config false;
        description
          "A list of the if:name of aggregation ports assigned to
         this key group.";
        reference
          "link-aggregation:key-groups";
      }
  
      container cscd {
        if-feature "ax:cscd";
        description
         "Contains CSCD parameters that need to be consistent for 
        all aggregation ports and aggregators in the key group.";
        leaf port-algorithm {
          type identityref  {       
            base ax:distribution-algorithm; 
          }
          default ax:unspecified;
          description
            "Identifies the algorithm used by the Aggregator to 
            assign frames to a Port Conversation ID.  Default is
            the value for an unspecified distribution algorithm.";
          reference
            "IEEE 802.1AX-2020, Clause 7.3.1.1.33";
        } 
        
        list admin-conv-service-map {
          key cid;
          description
            "Data structure to map service identifiers to 
            conversation identifiers.  Each entry consists of a 
            Conversation ID (CID) and a list of zero or more 
            Service Identifiers (SIDs) that map to it.";
          leaf cid {
            type uint16 {
              range 0..4095;  
            }
            description
             "Port Conversation Identifier";
          }
          leaf-list service-ids {
            type uint32;  
            description 
                "List of SIDs that are associated with the CID.";
          }
          reference
            "IEEE 802.1AX-2020, Clause 7.3.1.1.36, 6.6.3.1";
        } 
        leaf admin-conv-service-digest {
          type binary; 
          config false;
           description
            "The MD5 Digest of the admin-conv-service-map. The 
            value is NULL when the distribution algorithm  
            specified by agg-port-algorithm does not use the 
            admin-conv-service-map.";
          reference
            "IEEE 802.1AX-2020, Clause 7.3.1.1.39, 6.6.3.1";
        }
        list admin-conv-link-map {
          key cid;
          description
            "Data structure to map Conversation Identifiers to a 
            Link Number. Each entry consists of a Conversation ID 
            (CID) and a list of link numbers that can potentially 
            be selected for that CID. The value selected will be 
            the first link number in the list that is currently 
            operational.";
          leaf cid {
            type uint16 {
              range 0..4095;  
            }
            description
             "Port Conversation Identifier";
          }
          leaf-list link-numbers {
            type uint16;  
            description 
              "Ordered list of Link Numbers to carry packets with 
              this CID.";
          }
          reference
            "IEEE 802.1AX-2020, Clause 7.3.1.1.34, 6.6.3.1";
        } 
        leaf admin-conv-link-digest {
          type binary; 
          config false;
          description
            "The MD5 Digest of the admin-conv-link-map. The value 
            is NULL when the distribution algorithm specified by 
            agg-port-algorithm does not use the 
            admin-conv-link-map.";
          reference
            "IEEE 802.1AX-2020, Clause 7.3.1.1.38, 6.6.3.1";
        }
       
        leaf admin-discard-wrong-conv {   
          if-feature "ax:dwc";
          type enumeration {
            enum force-true {
              value 1;
              description
                "Indicates that an Aggregator should discard a 
                frame that is collected from an Aggregation Port 
                that is different from the Aggregation Port to 
                which the Aggregator would distribute a frame 
                with the same Port Converstion ID.";
            }
            enum force-false {
              value 2;
              description
                "Indicates that an Aggregator should not discard 
                a frame that is collected from an Aggregation Port
                that is different from the Aggregation Port to 
                which the Aggregator would distribute a frame with
                the same Port Converstion ID. This is the behavior
                of the Aggregator when DWC is not supported";
            }
            enum auto {
              value 3;
              description
                "Indicates that the Aggregator should behave as 
                if the value was force-true only when the actor  
                and partner agree on the algorithms (other than 
                unspecified) and mapping tables used to map frames
                to Aggregation Ports, and behave as if the value 
                was force-false otherwise.";
            }
          }
          default force-false;
          description
            "Indicates whether an Aggregator should discard a  
            frame that is collected from an Aggregation Port 
            that is different from the Aggregation Port to which 
            the Aggregator would distribute a frame with the 
            same Port Converstion ID.";
          reference
            "IEEE 802.1AX-2020, Clause 7.3.1.1.35, 6.6";
        } 
      } 

    } 
  } 


  augment "/if:interfaces/if:interface" {
    when 
      "derived-from-or-self(if:type,'ianaif:ieee8023adLag') or "+
      "if:type = 'ax:ieee8021axIrp'" {
        description
          "Applies to interfaces representing a LAG or 
          DRNI Intar-Relay Port.";
        }
    description
      "Augment Interface with Aggregator parameters.";
    container lag {
      description
        "Contains the Aggregator configuration information which
        provides the management controls necessary to allow an
        instance of an Aggregator to be managed.";
      leaf key-group-name {
        type key-group-ref;
        mandatory true;
        description
          "Specifies the entry in the link-aggregation key-groups 
          list to which this aggregator is assigned.";
      }
      leaf mac-address {
        type ieee:mac-address;
        config false;
        description
          "The MAC address assigned to the Aggregator.";
        reference
          "IEEE 802.1AX-2020, Clause 7.3.1.1.9";
      }
      container lacp {
        config false;
        description
          "Contains aggregator LACP operational data.";
        leaf actor-oper-key {
          type uint16;
          description
            "The current operational value of the Key for the
            Aggregator. The administrative Key value may differ
            from the operational Key value for the reasons
            discussed in 5.6.2. The meaning of particular Key
            values is of local significance.";
          reference
            "IEEE 802.1AX-2020, Clause 7.3.1.1.8";
        }
        leaf partner-system-id {
          type ieee:mac-address;
          description
            "Consisting of the unique identifier for the
            current protocol Partner of this Aggregator. A value
            of zero indicates that there is no known Partner.
            If the aggregation is manually configured, this
            System ID value will be a value assigned by the
            local System.";
          reference
            "IEEE 802.1AX-2020, Clause 7.3.1.1.10";
        }
        leaf partner-system-priority {
          type uint16;
          description
            "Indicates the priority value associated with the
            Partners System ID. If the aggregation is manually
            configured, this System Priority value will be a
            value assigned by the local System.";
          reference
            "IEEE 802.1AX-2020, Clause 7.3.1.1.11";
        }
        leaf partner-oper-key {
          type uint16;
          description
            "The current operational value of the Key for the
            Aggregators current protocol Partner. If the
            aggregation is manually configured, this Key value
            will be a value assigned by the local System.";
          reference
            "IEEE 802.1AX-2020, Clause 7.3.1.1.12";
        }
        leaf aggregate-or-individual {
          type boolean;
          description
            "Indicates whether the Aggregator represents an
            Aggregate (TRUE) or an Individual link (FALSE).";
          reference
            "IEEE 802.1AX-2020, Clause 7.3.1.1.6";
        }
      } 
      container cscd {
        if-feature "ax:cscd";
        config false;
        description
          "Aggregator parameters obtained by the operation of LACP 
          supporting CSCD.";
        leaf partner-port-algorithm {
          type identityref {
            base ax:distribution-algorithm;
          }
          description
            "Operational value of the distribution algorithm in 
            use by the LACP Partner.";
          reference
            "IEEE 802.1AX-2020, Clause 7.3.1.1.40";
        }
        leaf partner-conv-service-digest {
          type binary; 
          description
            "The MD5 Digest of the admin-conv-service-map in use 
            by the LACP Partner.";
          reference
            "IEEE 802.1AX-2020, Clause 7.3.1.1.42, Clause 6.6.3.1";
        }
        leaf partner-conv-link-digest {
          type binary; 
          description
            "The MD5 Digest of the admin-conv-link-map in use 
            by the LACP Partner.";
          reference
            "IEEE 802.1AX-2020, Clause 7.3.1.1.41, Clause 6.6.3.1";
        }
        leaf discard-wrong-conversation {
          type boolean;
          description
            "The operational value that determines whether an  
            Aggregator should discard a frame that is collected 
            from an Aggregation Port that is different from the  
            Aggregation Port to which the Aggregator would 
            distribute a frame with the same Port Conversation 
            ID.";
          reference
            "IEEE 802.1AX-2020, Clause 7.3.1.1.37, Clause 6.6";
        }
        leaf-list active-lag-links {
          type uint16;
          config false;
          description
            "A list, possibly empty, of the operational 
            link-number of each Aggregation Port active 
            (i.e. Collecting) on this Aggregator.";
          reference
            "IEEE 802.1AX-2020, Clause 7.3.1.1.43";
        }
      } 
    }
  }

  augment "/if:interfaces/if:interface/if:statistics" {
    when 
      "../dot1ax:lag" {
      description
        "Applies to aggregators.";
      }
    description
      "Augment interface statistics with aggregator statistics.";
    container lag-stats {
      config false;
      description
        "Contains the set of stats associated with the
        Aggregator.";
      leaf unknown-protocol-frames {
        type yang:counter64;
        description
          "A count of data frames discarded on reception by all
          ports that are (or have been) members of the
          aggregation, due to the detection of an unknown Slow
          Protocols PDU (7.3.3.1.5)";
        reference
          "IEEE 802.1AX-2020, Clause 7.3.1.1.29";
      }
    } 
  } 

  
  augment "/if:interfaces/if:interface" {
    description
      "Augment interface model with Aggregation port
      configuration nodes.";
    container aggport {
      presence
      "When present, this interface supports Link Aggregation";
      description
        "Contains Aggregation Port configuration related nodes,
        which provides the basic management controls necessary
        to allow an instance of an Aggregation Port to be managed,
        for the purposes of Link Aggregation.";

      leaf key-group-name {
        type key-group-ref;
        mandatory true;
        description
          "Specifies the entry in the link-aggregation key-groups 
          list to which this aggregation-port is assigned.";
      }
      leaf actor-port-number {
          type uint16 {
            range 1..65535;
          }
          description
            "The port number assigned to the Aggregation Port.
            The port number is communicated in LACPDUs as the
            Actor_Port.";
          reference
            "IEEE 802.1AX-2020, Clause 7.3.2.1.14, 6.4.6";        
      }
      leaf actor-port-priority {
        type uint16;
        default 0;
        description
          "The priority value assigned to this Aggregation Port.";
        reference
          "IEEE 802.1AX-2020, Clause 7.3.2.1.15, 6.4.6";
      }
      leaf actor-admin-state {
        type ax:lacp-state;
        default "lacp-activity aggregation";
        description
          "Corresponding to the administrative values of the
          first three bits (positions 0, 1, and 2) of Actor_State 
          as transmitted by the Actor in LACPDUs. Provides 
          administrative control over the values of the 
          LACP_Activity, LACP_Timeout, and Aggregation state. 
          Setting the LACP_Activity state to '0' ensures that the 
          transmission of LACPDUs is controlled by the 
          partner-oper-state.LACP_Activity.
          Setting the LACP_Timeout to '0' ensures that actor uses 
          the Long_Timeout value, allowing the partner to transmit 
          LACPDUs at the Slow_Periodic_Time.  
          Setting the Aggregation state to '0' ensures that this 
          port will not be aggregated with any other ports. 
          The remaining five bits (corresponding to 
          Synchronization, Collecting, Distributing, Expired, 
          and Defaulted) are ignored.";
        reference
          "IEEE 802.1AX-2020, Clause 7.3.2.1.20, 6.4.1, 6.4.2.2, 
          6.4.6";
      }

      leaf partner-admin-key {
        type uint16;
        description
          "The current administrative value of the Key for the
          protocol Partner. The assigned value is used, along 
          with the value of port-partner-admin-system-priority,
          partner-admin-system-id, partner-admin-port, and
          partner-admin-port-priority, in order to achieve
          manually configured aggregation.;";
        reference
          "IEEE 802.1AX-2020, Clause 7.3.2.1.10";
      }
      leaf partner-admin-port {
        type uint16;
        description
          "The current administrative value of the port number for
          the protocol Partner. The assigned value is used, along
          with the value of partner-admin-system-priority,
          partner-admin-system-id, port-partner-admin-key, and
          partner-admin-port-priority, in order to achieve
          manually configured aggregation.";
        reference
          "IEEE 802.1AX-2020, Clause 7.3.2.1.16";
      }
      leaf partner-admin-port-priority {
        type uint16;
        default 0;
        description
          "The current administrative value of the port priority
          for the protocol Partner. The assigned value is used,
          along with the value of partner-admin-system-priority,
          partner-admin-system-id, partner-admin-key, and
          partner-admin-port, in order to achieve manually
          configured aggregation.";
        reference
          "IEEE 802.1AX-2020, Clause 7.3.2.1.18";
      }
      leaf partner-admin-state {
        type ax:lacp-state;
        default "synchronization";  
        description
          "Corresponding to the administrative values of the first
          four bits (positions 0, 1, 2, and 3) of Partner_State to
          be used when no LACPDUs are received from LACP partner. 
          Provides administrative control over the partner's
          LACP_Activity, LACP_Timeout, Aggregation, and  
          Synchronization state when the partner's information is 
          unknown (i.e. no LACPDUs are received from the partner). 
          Setting the LACP_Activity state to '0' ensures that the 
          transmission of LACPDUs is controlled by the 
          actor-admin-state.LACP_Activity.
          Setting the LACP_Timeout to '0' ensures that LACPDUs 
          will be transmitted at the Slow_Periodic_Time.  
          Setting the Aggregation state to '0' ensures that this 
          port will not be aggregated with any other ports. 
          Setting the Synchronization state to '0' prevents this 
          port from becoming active.
          The remaining four bits (corresponding to Collecting,  
          Distributing, Expired, and Defaulted) are ignored.";
        reference
          "IEEE 802.1AX-2020, Clause 7.3.2.1.22, 6.4.1, 6.4.2.2, 
          6.4.6";
      }

      leaf wtr-time {
        type uint16;
        default 1;
        description
          "The wait-to-restore (WTR) period, in seconds, that 
           needs to elapse between an Aggregation Port on a LAG 
           coming up (Port_Operational becoming TRUE) and being 
           permitted to become active (transmitting and 
           receiving frames) on the LAG.";
        reference
          "IEEE 802.1AX-2020, Clause 7.3.2.1.30";
      }
      leaf wtr-revertive {
        type boolean;
        default true;
        description
          "Controls revertive or non-revertive mode of operation. 
           When TRUE, the Aggregation Port can become active as 
           soon as the wait-to-restore timer expires regardless of 
           the state of other links in the LAG. 
           When FALSE, the Aggregation Port cannot become active 
           unless there are no other links that can become active 
           in the LAG. The default value is TRUE.";
        reference
          "IEEE 802.1AX-2020, Clause 7.3.2.1.31";
      }

      container lacp {
        config false;
        description
          "Contains Aggregation port LACP operational related
          nodes.";
        leaf actor-lacp-version {
          type uint16;
          description
            "The version number transmitted in LACPDUs on this 
            Aggregation Port";
          reference
            "IEEE 802.1AX-2020, Clause 7.3.2.1.33";
        }
        leaf actor-oper-key {
          type uint16;
          description
            "The current operational value of the Key for the
            Aggregation Port. The meaning of particular Key values
            is of local significance.";
          reference
            "IEEE 802.1AX-2020, Clause 7.3.2.1.5";
        }
        leaf actor-oper-state {
          type ax:lacp-state;
          description
            "The operational value of the Actor_State as 
            transmitted in LACPDUs.";
          reference
            "IEEE 802.1AX-2020, Clause 7.3.2.1.21, 6.4.1, 6.4.2.2, 
            6.4.6";
        }
        leaf partner-lacp-version {
          type uint16;
          description
            "The version number in the LACPDU most recently 
            received on this Aggregation Port.";
          reference
            "IEEE 802.1AX-2020, Clause 7.3.2.1.34";
        }
        leaf partner-oper-system-priority {
          type uint16;
          description
            "Indicates the operational value of priority associated
            with the Partners System ID. The value of this 
            attribute may contain the manually configured value 
            carried in partner-admin-system-priority if there is 
            no protocol Partner.";
          reference
            "IEEE 802.1AX-2020, Clause 7.3.2.1.7";
        }
        leaf partner-oper-system-id {
          type ieee:mac-address;
          description
            "Represents the current value of the Aggregation
            Ports protocol Partners System ID. A value of zero
            indicates that there is no known protocol Partner. The
            value of this attribute may contain the manually
            configured value carried in partner-admin-system-id if
            there is no protocol Partner.";
          reference
            "IEEE 802.1AX-2020, Clause 7.3.2.1.9";
        }
        leaf partner-oper-key {
          type uint16;
          description
            "The current operational value of the Key for the
            protocol Partner. The value of this attribute may
            contain the manually configured value carried in
            partner-admin-key if there is no protocol Partner.";
          reference
            "IEEE 802.1AX-2020, Clause 7.3.2.1.11";
        }
        leaf partner-oper-port {
          type uint16;
          description
            "The operational port number assigned by the 
            Aggregation Port's protocol Partner. The value of this 
            attribute may contain the administratively configured 
            value carried in partner-admin-port if there is no 
            protocol Partner.";
          reference
            "IEEE 802.1AX-2020, Clause 7.3.2.1.17";
        }
        leaf partner-oper-port-priority {
          type uint16;
          description
            "The operational priority value assigned by the 
            Aggregation Port's protocol Partner. The value of this 
            attribute may contain the administratively configured 
            value carried in partner-admin-port-priority if there 
            is no protocol Partner.";
          reference
            "IEEE 802.1AX-2020, Clause 7.3.2.1.19";
        }
        leaf partner-oper-state {
          type ax:lacp-state;
          description
            "The operational value of the partner's LACP state 
            derived from received LACPDUs or, when Defaulted is 
            true, from the partner-admin-state.";
          reference
            "IEEE 802.1AX-2020, Clause 7.3.2.1.23, 6.4.1, 6.4.2.2, 
            6.4.6";
        }
        leaf aggregate-or-individual {
          type boolean;
          description
            "When true indicates the Aggregation Port can join a 
            LAG consisting of multiple Aggregation Ports. 
            When false, indicates that the Aggregation Port can 
            only operate as an Solitary link because the
            Aggregation bit is false in either 
            actor-oper-port-state or partner-oper-port-state.";
          reference
            "IEEE 802.1AX-2020, Clause 7.3.2.1.24";
        }
        leaf wtr-waiting {
          type boolean;
          description
            "Indicates the Aggregation Port is inhibited from 
            becoming active for an interval (determined by 
            wtr-time) after becoming operational or while  
            non-revertive operation is being enforced by the 
            Selection Logic.";
          reference
            "IEEE 802.1AX-2020, Clause 7.3.2.32";
        }
      } 

      container cscd {
        if-feature "ax:cscd";
        description
          "Aggregation port parameters for support of CSCD.";        
        leaf admin-link-number {
          type uint16;
          description
            "The Link_Number value for the Aggregation Port, 
            configured by the System's administrator, which is 
            unique among all Aggregation Ports in the same key
            group, and selected from the set of Link_Numbers in 
            the admin-conv-link-map of that key group.

            More than one Aggregation Port in a LAG having the same
            Admin_Link_Number can, if Discard_Wrong_Conversation 
            is TRUE, result in significant frame loss. If the 
            Admin_Link_Number is not in the set of Link_Numbers  
            in the Admin_Conv_Link_Map, then no frames will be 
            distributed to this Aggregation Port. A value of 0 
            will result in no frames are distributed to this 
            Aggregation Port.

            From an implementation standpoint, this can be be 
            automatically determined and set by the system.  
            This optional leaf allows for administrative
            control over numbering.";
          reference
            "IEEE 802.1AX-2020, Clause 7.3.2.1.27";
        }
        leaf partner-link-number {
          type uint16;
          config false;
          description
            "The last received value of the Partner_Link_Number, 
            or zero if the Aggregation Port is using default 
            values for the Partner or the Partner LACP Version 
            is 1.";
          reference
            "IEEE 802.1AX-2020, Clause 7.3.2.1.29";
        }
        leaf link-number {
          type uint16;
          config false;
          description 
            "The operational link number for this Aggregation Port.
            The value is either the same as the admin-link-number,
            or the corresponding value fo the LACP partner.";
          reference
            "IEEE 802.1AX-2020, Clause 7.3.2.1.28";
        }
        leaf oper-conversation-passes {
          type binary;
          config false;
          description
            "A vector of Boolean values, with one value for each 
            possible Port Conversation ID. A 1 indicates that a  
            frame mapping to this Port Conversation ID is 
            distributed to this Aggregation Port, and a 0 
            indicates that it is not";
          reference
            "IEEE 802.1AX-2020, Clause 7.3.2.1.25";
        }
        leaf oper-conversation-collected {
          type binary;
          config false;
          description
            "A vector of Boolean values, with one value for each 
            possible Port Conversation ID. A 1 indicates that a  
            frame mapping to this Port Conversation ID can be 
            collected from  this Aggregation Port, and a 0 
            indicates that it cannot";
          reference
            "IEEE 802.1AX-2020, Clause 7.3.2.1.26";
        }
      } 
    }
  }

  augment "/if:interfaces/if:interface/if:statistics" {
    when 
      "../dot1ax:aggport" {
      description
        "Applies to aggregation ports.";
      }
    description
      "Augment interface statistics with aggport statistics.";
    container aggport-stats {
      config false;
      description
        "Contains stats associated with the Aggregation Port.";
      leaf lacp-pdu-rx {
        type yang:counter64;
        description
          "The number of valid LACPDUs received on this
          Aggregation Port.";
        reference
          "IEEE 802.1AX-2020, Clause 7.3.3.1.2";
      }
      leaf marker-pdu-rx {
        type yang:counter64;
        description
          "The number of valid Marker PDUs received on this
          Aggregation Port.";
        reference
          "IEEE 802.1AX-2020, Clause 7.3.3.1.3";
      }
      leaf marker-response-pdu-rx {
        type yang:counter64;
        description
          "The number of valid Marker Response PDUs received on
          this Aggregation Port.";
        reference
          "IEEE 802.1AX-2020, Clause 7.3.3.1.4";
      }
      leaf unknown-rx {
        type yang:counter64;
        description
          "The number of frames received that either:
          a) Carry the Slow Protocols Ethernet Type value (IEEE
          Std 802.3 Annex 57A.4), but contain an unknown PDU, or
          b) Are addressed to the Slow Protocols group MAC
          Address (IEEE Std 802.3 Annex 57A.3), but do not carry
          the Slow Protocols Ethernet Type.";
        reference
          "IEEE 802.1AX-2020, Clause 7.3.3.1.5";
      }
      leaf illegal-rx {
       type yang:counter64;
        description
          "The number of frames received that carry the Slow
          Protocols Ethernet Type value (IEEE Std 802.3 Annex
          57A.4), but contain a badly formed PDU or an illegal
          value of Protocol Subtype (IEEE Std 802.3 Annex
          57A.3).";
        reference
          "IEEE 802.1AX-2020, Clause 7.3.3.1.6";
      }
      leaf lacp-pdu-tx {
        type yang:counter64;
        description
          "The number of LACPDUs transmitted on this
          Aggregation Port.";
        reference
          "IEEE 802.1AX-2020, Clause 7.3.3.1.7";
      }
      leaf marker-pdu-tx {
        type yang:counter64;
        description
          "The number of Marker PDUs transmitted on this
          Aggregation Port.";
        reference
          "IEEE 802.1AX-2020, Clause 7.3.3.1.8";
      }
      leaf marker-response-pdu-tx {
        type yang:counter64;
        description
          "The number of Marker Response PDUs transmitted on
          this Aggregation Port.";
        reference
          "IEEE 802.1AX-2020, Clause 7.3.3.1.9";
      }
    } 
  } 

}
