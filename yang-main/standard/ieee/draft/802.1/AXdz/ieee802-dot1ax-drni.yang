module ieee802-dot1ax-drni {
  yang-version 1.1;
  namespace "urn:ieee:params:xml:ns:yang:ieee802-dot1ax-drni";
  prefix "dot1ax-drni";

  import ieee802-dot1ax-types {
    prefix "ax";
  }
  import ieee802-dot1ax-linkagg {
    prefix "dot1ax";
  }
  import ieee802-types {
    prefix "ieee";
  }
  import ietf-yang-types {
    prefix "yang";
  }
  import ietf-interfaces {
    prefix "if";
  }

  organization
    "Institute of Electrical and Electronics Engineers";

  contact
      "Web URL: http://www.ieee802.org/1/

       Working Group Chair:
        Glenn Parsons
        glenn.parsons@ericsson.com

       Editor:
         Stephen Haddock
         shaddock@stanfordalumni.org";

  description
    "This YANG module describes the configuration model for a 
    Distributed Resilient Network Interface (DRNI) as specified
    in 802.1AX.
    
    Copyright (C) IEEE (2024).
    
    This version of this YANG module is part of IEEE Std 802.1AX;
    see the standard itself for full legal notices.";

  revision "2024-06-05" {
    description
      "For task group ballot on draft 0.1";
    reference
      "IEEE 802.1AX-2020, Link Aggregation.";
  }
  revision "2024-05-04" {
    description
      "Initial Version.";
    reference
      "IEEE 802.1AX-2020, Link Aggregation.";
  }


  augment "/if:interfaces/if:interface/dot1ax:lag" {
    description 
      "Augmentation parameters only for Aggregators with
      DRNI enabled.";
    container drni {
      presence
      "When present, this Aggregator is enabled for DRNI";
      description
        "Aggregator parameters to support a Distributed 
        Resilient Network Interface";
      leaf irp-name {
        type if:interface-ref;
        mandatory true;
        description
          "Interface Name (if:name) of the Port supporting the
           Intra Relay Port (IRP) of this DRNI Gateway.";
        reference
          "IEEE 802.1AX-2020, Clause 7.4.1.1.23";
      }
      leaf drni-aggregator-key {
        type uint16;
        description
          "The Aggregator Key value to be used by the Aggregator
          supporting this DRNI Gateway (and the Aggregation Ports
          assigned to this DRNI Gateway) when paired with a 
          neighbor DRNI System via the IRC. ";
        reference
          "IEEE 802.1AX-2020, Clause 7.4.1.1.15";
        }
      leaf drni-aggregator-system {
        type ieee:mac-address;
        default "00-00-00-00-00-00";
        description
          "The Aggregator System value to be used by the 
          Aggregator supporting this DRNI Gateway (and the 
          Aggregation Ports assigned to this DRNI Gateway) 
          when paired with a neighborDRNI System via the 
          Intra-Relay Connection (IRC).";
        reference
          "IEEE 802.1AX-2020, Clause 7.4.1.1.13";
      }
      leaf drni-aggregator-system-priority {
        type uint16;
        default 0;
        description
          "The Aggregator System Priority value to be used by the
           Aggregator supporting this DRNI Gateway (and the
           Aggregation Ports assigned to this DRNI Gateway) when
           paired with a neighbor DRNI System via the IRC.";
        reference
          "IEEE 802.1AX-2020, Clause 7.4.1.1.14";
      }
      leaf drcp-protocol-da {
        type ieee:mac-address;
        must 
          '. = "01-80-c2-00-00-00" or . = "01-80-C2-00-00-00" or
           . = "01-80-c2-00-00-0e" or . = "01-80-C2-00-00-0E" or
           . = "01-80-c2-00-00-03" or . = "01-80-C2-00-00-03"' {
            error-message "Invalid protocol address";
        }
        default "01-80-c2-00-00-03";  
        description
          "A 6-octet read-write MAC Address value specifying the 
          Destination Address for Distributed Relay Control PDUs 
          transmitted on the Intra-Relay Port. Valid addresses are 
          the Nearest Customer Bridge, Nearest Bridge, and
          Nearest non-TPMR Bridge group addresses.  The default
          value shall be the Nearest Non-TPMR Bridge group 
          address.";
        reference
          "IEEE 802.1AX-2020, Clause 7.4.1.1.12, Clause 9.6.1.1";
      }
      leaf home-admin-irp-state {
        type ax:irp-state;
        default "short-timeout irc-data";  
        description
            "A string of 8 bits, corresponding to the values of
             IRP_State. These values allow administrative control 
             over the Short_Timeout and IRC_Data flags.";
          reference
            "IEEE 802.1AX-2020, Clause 7.4.1.1.24, 9.6.2.3, 
            Figure 9-13";
      }
      leaf home-oper-irp-state {
        type ax:irp-state;
        config false;
        description
          "A string of 8 bits, corresponding to the current
           operational value of IRP_State as transmitted in 
           DRCPDUs.";
        reference
          "IEEE 802.1AX-2020, Clause 7.4.1.1.25, 9.6.2.3, 
          Figure 9-13";
      }
      leaf home-cscd-gateway-control {
        type boolean;
        default true;
        description
          "When TRUE, allows the DRNI Gateway Port selection to 
           be based on the CSCD parameters that control the 
           Aggregator Port selection.";
        reference
          "IEEE 802.1AX-2020, Clause 7.4.1.1.16";
      }
      leaf home-dr-client-gateway-control {
        type boolean;
        default true;
        description
          "When TRUE, allows the Distributed Relay Client to
           determine whether to forward frames through the DRNI
           Gateway Port.";
        reference
          "IEEE 802.1AX-2020, Clause 7.4.1.1.17";
      }
      leaf home-gateway-algorithm {
        type identityref  {       
         base ax:distribution-algorithm; 
        }
        default ax:unspecified;
        description
          "Identifies the algorithm used by the DRNI Gateway to 
          assign frames to a Gateway Conversation ID. 8.2 provides
          the IEEE 802.1 OUI (00-80-C2) Gateway Algorithm 
          encodings.  Default is the value for an unspecified 
          distribution algorithm.";
        reference
          "IEEE 802.1AX-2020, Clause 7.4.1.1.6";
      } 
        
      list home-admin-conv-service-map { 
        key cid;
        description
          "Data structure to map service identifiers to 
          conversation identifiers.Each entry consists of a 
          Conversation ID (CID) and a list of zero or more Service
          Identifiers (SIDs) that map to it. Frames with Service
          IDs not contained in the map are not mapped to any
          Gateway Conversation ID and are discarded.";
        leaf cid {
          type uint16 {
            range 0..4095;  
          }
          description
           "Port Conversation Identifier";
        }
        leaf-list service-ids {
          type uint32;  
          description 
            "List of SIDs that are associated with the CID.";
        }
        reference
          "IEEE 802.1AX-2020, Clause 7.4.1.1.20, Clause 6.6.3.1";
      } 
      leaf home-admin-conv-service-digest {
        type binary; 
        config false;
        description
          "The MD5 Digest of the home-admin-conv-service-map. The 
          value is NULL when the distribution algorithm specified 
          by agg-port-algorithm does not use the 
          home-admin-conv-service-map.";
        reference
          "IEEE 802.1AX-2020, Clause 7.4.1.1.21";
      }
      container gateway-enable-mask {
        uses drni-mask;
        description
          "A vector of Boolean values, with one value for each 
          possible Gateway Conversation ID. A 1 indicates that
          frames associated with that Gateway Conversation ID
          are allowed to pass through this Gateway Port, and a
          0 indicates that such frames are not allowed to pass.
          Default value is all bits set to 1.";
        reference
          "IEEE 802.1AX-2020, Clause 7.4.1.1.18, 9.5.3.5, 9.6.5";
      }

      container gateway-preference-mask {
        uses drni-mask;
        description
          "A vector of Boolean values, with one value for each 
          possible Gateway Conversation ID. A 1 indicates that
          this Gateway Port is the preferred Gateway when both
          DRNI Gateways have the Gateway Conversation ID enabled
          in the gateway-available-mask, and a 0 indicates that
          it is not preferred.
          Default value is all bits set to 1.";
        reference
          "IEEE 802.1AX-2020, Clause 7.4.1.1.19, 9.5.3.5, 9.6.5";
      }
      leaf gateway-available-mask {
        type binary;
        config false;
        description
          "A vector of Boolean values, with one value for each 
          possible Gateway Conversation ID. A 1 indicates that
          this Gateway Port is eligible to be selected to pass
          that Gateway Conversation ID, and a 0 indicates that
          it is not eligible.";
        reference
          "IEEE 802.1AX-2020, Clause 7.4.1.1.22, 9.5.3.5, 9.6.5";
      }

      container neighbor {
        config false;
        description
          "Operational values for the DRNI neighbor obtained 
          from DRCPDUs.";
        leaf oper-irp-state {
          type ax:irp-state;
          description
            "A string of 8 bits, corresponding to the current
            operational value of IRP_State as transmitted in
            DRCPDUs.";
          reference
            "IEEE 802.1AX-2020, Clause 7.4.1.1.25, 9.6.2.3, 
            Figure 9-13";
        }
        leaf system {
          type ieee:mac-address;
          description
            "The MAC Address portion of the System Identifier of
            the Neighbor DRNI System (connected via the 
            Intra-Relay Port). ";
          reference
            "IEEE 802.1AX-2020, Clause 7.4.1.1.29";
        }
        leaf system-priority {
          type uint16;
          description
            "The priority portion of the System Identifier of the
            Neighbor DRNI System (connected via the Intra-Relay 
            Port).";
          reference
            "IEEE 802.1AX-2020, Clause 7.4.1.1.30";
        }
        leaf drni-key {
          type uint16;
          description
            "The DRNI key value received from the Neighbor DRNI 
            System (connected via the IntraRelay Port).";
          reference
            "IEEE 802.1AX-2020, Clause 7.4.1.1.31";
        }
        leaf aggregator-algorithm {
          type identityref  {   
            base ax:distribution-algorithm;
          }
          description
            "The Port algorithm used by the Neighbor Aggregator to
            assign frames to Port Conversation IDs.";
          reference
            "IEEE 802.1AX-2020, Clause 7.4.1.1.33";
        }
        leaf aggregator-conv-service-digest {
          type binary; 
          config false;
          description
            "The MD5 Digest of the Neighbor Aggregator’s  
            Admin_Conv_Service_Map. Obtained from the Home  
            Aggregator State TLV last received from the Neighbor 
            DRNI System.";
          reference
            "IEEE 802.1AX-2020, Clause 7.4.1.1.34";
        }
        leaf aggregator-conv-link-digest {
          type binary; 
          config false;
          description
            "The MD5 Digest of the Neighbor Aggregator’s 
            Admin_Conv_Link_Map. Obtained from the Home Aggregator
            State TLV (9.6.2.4) last received from the Neighbor 
            DRNI System.";
          reference
            "IEEE 802.1AX-2020, Clause 7.4.1.1.35";
        }
        leaf partner-system-priority {
          type uint16;
          description
            "The priority portion of the System Identifier of the
            Neighbor Aggregator's Partner.";
          reference
            "IEEE 802.1AX-2020, Clause 7.4.1.1.36";
        }
        leaf partner-system {
          type ieee:mac-address;
          description
            "The MAC Address portion of the System Identifier of 
            the Neighbor Aggregator's Partner.";
          reference
            "IEEE 802.1AX-2020, Clause 7.4.1.1.37";
        }
        leaf partner-aggregator-key {
          type uint16;
          description
            "The operational key value of the Neighbor 
            Aggregator's Partner.";
          reference
            "IEEE 802.1AX-2020, Clause 7.4.1.1.38";
        }
        leaf cscd-state {
          type bits {
            bit reserved-1 {
              position 0;
              description
                "Bit 1 is reserved for future use. It is set to 0
                and ignored on receipt.";
            }
            bit reserved-2 {
              position 1;
              description
                "Bit 2 is reserved for future use. It is set to 0 
                and ignored on receipt.";
            }
            bit reserved-3 {
              position 2;
              description
                "Bit 3 is reserved for future use. It is set to 0 
                and ignored on receipt.";
            }
            bit cscd_gateway_control {
              position 3;
              description
                "CSCD_Gateway_Control is encoded in bit 4. When 
                this flag is TRUE, the DRNI Gateway is configured 
                to minimize forwarding data frames on the IRC by
                selecting the DRNI Gateway and Aggregator Ports 
                for forwarding any given Conversation ID to be in 
                the same DRNI System.";
            }
            bit discard_wrong_conversation {
              position 4;
              description
                "Discard_Wrong_Conversation is encoded in bit 5. 
                The Aggregator's Discard_Wrong_Conversation 
                value.";
            }
            bit differ_conv_link_digests {
              position 5;
              description
                "Differ_Conv_Link_Digests is encoded in bit 6. 
                This flag is TRUE when the Aggregator's 
                Actor_Conv_Link_Digest matches the Aggregator's 
                Partner_Conv_Link_Digest.";
            }
            bit differ_conv_service_digests {
              position 6;
              description
                "Differ_Conv_Service_Digests is encoded in bit 7.
                This flag is TRUE when the Aggregator's 
                Actor_Conv_Service_Digest matches the Aggregator's
                Partner_Conv_Service_Digest.";
            }
            bit differ_port_algorithms {
              position 7;
              description
                "Differ_Port_Algorithms is encoded in bit 8. The
                Aggregator's differPortAlgorithms flag is TRUE 
                when the Aggregator's Actor_Port_Algorithm matches
                the Aggregator's Partner_Port_Algorithm.";
            }
          }
          description
            "8 bits, corresponding to the Aggregator_CSCD_State 
            in the Neighbor_Aggregator_State variable. The first 
            three bits (the least significant bits of CSCD_State) 
            are reserved; the fourth bit corresponds to the 
            Neighbor's value for Home_Admin_CSCD_Gateway_Control; 
            the fifth bit corresponds to the Neighbor Aggregator's
            operational value for Discard_Wrong_Conversation; and 
            the sixth, seventh, and eighth bits correspond to the 
            Neighbor Aggregator's operational value for 
            differConvLinkDigests, differConvServiceDigests, and 
            differPortAlgorithms, respectively, (the most 
            significant bits of CSCD_State).";
          reference
            "IEEE 802.1AX-2020, Clause 7.4.1.1.39";
        }
        leaf-list active-links {
          type uint16;
          description
            "A list of the operational Link_Numbers of Aggregation
            Ports that are currently active (i.e., collecting) on
            the Neighbor’s Aggregator. An empty list indicates that
            there are no Aggregation Ports active. Each integer 
            value in the list carries an aAggPortOperLinkNumber 
            attribute value.";
          reference
            "IEEE 802.1AX-2020, Clause 7.4.1.1.40 ";
        }
        leaf gateway-algorithm {
          type identityref  {
            base ax:distribution-algorithm;
          }
          description
            "The gateway algorithm used by the Neighbor DRNI 
            Gateway to assign frames to Gateway Conversation IDs.";
          reference
            "IEEE 802.1AX-2020, Clause 7.4.1.1.41";
        }
        leaf gateway-conv-service-digest {
          type binary; 
          description
            "The MD5 Digest of the Neighbor DRNI Gateway’s 
            the Home_Admin_Gateway_Conv_Service_Map. Obtained  
            from Gateway_Conv_Service_Digest in the 
            Neighbor_Gateway_State TLV last received from the 
            Neighbor DRNI System.";
          reference
            "IEEE 802.1AX-2020, Clause 7.4.1.1.42";
        }
        leaf gateway-available-mask {
          type binary;
          description
            "A vector of Boolean values, with one value for each 
            possible Gateway Conversation ID. A 1 indicates that
            the Neighbor DRNI Gateway Port is eligible to be 
            selected to pass that Gateway Conversation ID, and
            a 0 indicates that it is not eligible.";
          reference
            "IEEE 802.1AX-2020, Clause 7.4.1.1.43";
        }
        leaf gateway-preference-mask {
          type binary;
          description
            "A vector of Boolean values, with one value for each 
            possible Gateway Conversation ID. A 1 indicates that
            the Neighbor DRNI Gateway Port is the preferred  
            Gateway when both DRNI Gateways have the Gateway 
            Conversation ID enabled in the gateway-available-mask,
            and a 0 indicates that it is not preferred.";
          reference
            "IEEE 802.1AX-2020, Clause 7.4.1.1.44";
        }
      }

      container gateway-relay {
        config false;
        description 
          "The set of masks, indexed by CID that determine the 
          forwarding of frames by the DRNI Gateway Relay.";
        leaf home-aggregator-mask {
          type binary;
          description
            "A vector of Boolean values, with one value for each 
            possible Port Conversation ID. A 1 indicates that the 
            Port Conversation ID is allowed to be distributed
            through this DRNI Gateway’s Aggregator, and a 0 
            indicates that it cannot";
          reference
            "IEEE 802.1AX-2020, Clause 7.4.1.1.7, 9.5.2.2";
        }
        leaf home-gateway-mask {
          type binary;
          description
            "A vector of Boolean values, with one value for each 
            possible Port Conversation ID. A 1 indicates that the 
            Port Conversation ID is allowed to pass through this
            DRNI Gateway Port, and a 0 indicates that it cannot";
          reference
            "IEEE 802.1AX-2020, Clause 7.4.1.1.8, 9.5.2.2";
        }
         leaf neighbor-aggregator-mask {
          type binary;
          description
            "A vector of Boolean values, with one value for each 
            possible Port Conversation ID. A 1 indicates that the 
            Port Conversation ID is allowed to be distributed
            through the IRP to the Neighbor Aggregator, and a 0 
            indicates that it is not";
          reference
            "IEEE 802.1AX-2020, Clause 7.4.1.1.27, 9.5.2.2";
        }
        leaf neighbor-gateway-mask {
          type binary;
          description
            "A vector of Boolean values, with one value for each 
            possible Port Conversation ID. A 1 indicates that the 
            Port Conversation ID is allowed to be passed to the
            Neighborr DRNI Gateway Port via the IRP, and a 0 
            indicates that it is not";
          reference
            "IEEE 802.1AX-2020, Clause 7.4.1.1.28, 9.5.2.2";
        }
      }
    }
  }

    augment "/if:interfaces/if:interface/if:statistics" {
      when 
        "../dot1ax:lag/dot1ax-drni:drni" {

      description
          "Applies to aggregators with DRNI present.";
        }
    description
      "Augment interface statistics with DRNI statistics.";
    container drni-stats {
      description
        "Contains DRNI specific statistics.";

      leaf drcpdus-rx {
        type yang:counter64;
        config false;
        description
          "The number of valid DRCPDUs received on this
          Intra-Relay Port.";
        reference
          "IEEE 802.1AX-2020, Clause 7.4.1.1.45";
      }
      leaf illegal-rx {
        type yang:counter64;
        config false;
        description
          "The number of frames received on this Intra-Relay 
          Port that carry the DRCP EtherType value, 
          but contain a badly formed PDU.";
        reference
          "IEEE 802.1AX-2020, Clause 7.4.1.1.46, 9.6.1.4";
      }
      leaf drcpdus-tx {
        type yang:counter64;
        config false;
        description
          "The number of valid DRCPDUs transmitted on this
          Intra-Relay Port.";
        reference
          "IEEE 802.1AX-2020, Clause 7.4.1.1.47";
      }
    }
  }

    grouping drni-mask {
    description
      "Specifies the contents of a bit mask indexed by CID.";
    choice method {
      default pattern;
      description
        "Provides three ways to specify the mask contents.";
      leaf pattern {
        type identityref {
          base ax:drni-mask-patterns;
        }
        default ax:all-ones;
        // Could not get this default statement to pass yanglint
        //   if grouping was specified in ieee802-dot1ax-types
        description
          "Use a predefined pattern to fill the mask.";
      }
      leaf-list cid-list {
        type uint16 {
          range 0..4095;
        }
        description
          "A list of CIDs whose corresponding bit in the 
          mask should be set to one.";
      }
      leaf mask {
        type binary {
          length 512;
        }
        description
          "Specify an explicit mask for all 4096 CID values.";
      }
    }
    leaf invert-list {
      type boolean;
      default false;
      description
        "When true the mask derived from one of the options
        above will be inverted: each zero replaced with a one,
        and each one replaced with a zero.";
    }
  }

}
